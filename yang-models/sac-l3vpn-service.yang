module sac-l3vpn-service {
  yang-version 1.1;
  namespace "http://github.com/rgoldens/cisco-live-2026/sac-l3vpn-service";
  prefix "sac-l3vpn";

  organization "Cisco Live 2026 - Service as Code Lab";
  contact "Ryan Goldenstein <rgoldens@cisco.com>";

  description
    "YANG data model for L3VPN service definitions in the Service as Code lab.
     This model defines the schema for customer VPN services, including
     VRF configuration, route targets, PE interface bindings, and BGP parameters.
     
     The model is validated against YAML service definitions to ensure
     required fields are present and values conform to network constraints.";

  revision 2026-03-01 {
    description "Initial version for Cisco Live 2026 lab";
    reference "Service as Code: YANG Validation in GitOps Pipelines";
  }

  container services {
    description "Root container for all network services";

    container l3vpn {
      description "Layer 3 VPN service definitions";

      list customer {
        key "customer-name";
        description "Individual customer L3VPN services";

        leaf customer-name {
          type string {
            pattern '[A-Za-z][A-Za-z0-9_-]*';
          }
          description "Human-readable customer name (e.g., CustomerA, CUST_B)";
          mandatory true;
        }

        leaf vrf {
          type string {
            pattern '[A-Z0-9_]{1,32}';
            length "1..32";
          }
          description "VRF name on PE routers (must be uppercase alphanumeric, max 32 chars)";
          mandatory true;
        }

        leaf rd {
          type string {
            pattern '[0-9]+:[0-9]+';
          }
          description "Route Distinguisher in format ASN:value or IP:value (e.g., 65000:100)";
          mandatory true;
        }

        leaf rt-import {
          type string {
            pattern '[0-9]+:[0-9]+';
          }
          description "Route Target for import in format ASN:value (e.g., 65000:100)";
          mandatory true;
        }

        leaf rt-export {
          type string {
            pattern '[0-9]+:[0-9]+';
          }
          description "Route Target for export in format ASN:value (e.g., 65000:100)";
          mandatory true;
        }

        container pe-interfaces {
          description "PE router interface bindings for this VPN";
          mandatory true;

          list interface {
            key "pe-name";
            description "L3 interface on a PE router bound to this VRF";
            min-elements 1;

            leaf pe-name {
              type string {
                pattern 'csr-pe[0-9]{2}';
              }
              description "PE router name (e.g., csr-pe01, csr-pe02)";
              mandatory true;
            }

            leaf interface-name {
              type string {
                pattern 'GigabitEthernet[0-9]+/[0-9]+/[0-9]+(\.[0-9]+)?';
              }
              description "Physical or subinterface name (e.g., GigabitEthernet0/0/1, GigabitEthernet0/0/1.100)";
              mandatory true;
            }

            leaf pe-ip {
              type string {
                pattern '([0-9]{1,3}\.){3}[0-9]{1,3}/[0-9]{1,2}';
              }
              description "PE-side IP address and prefix length (CIDR notation, e.g., 192.168.100.1/24)";
              mandatory true;
            }

            leaf ce-neighbor {
              type string {
                pattern '([0-9]{1,3}\.){3}[0-9]{1,3}';
              }
              description "CE neighbor IP address for BGP peering (e.g., 192.168.100.2)";
              mandatory true;
            }

            leaf ce-asn {
              type uint32 {
                range "1..4200000000";
              }
              description "CE autonomous system number for BGP";
              mandatory true;
            }
          }
        }

        container expected-prefixes {
          description "Prefixes expected to be learned via BGP for validation";

          leaf-list prefix {
            type string {
              pattern '([0-9]{1,3}\.){3}[0-9]{1,3}/[0-9]{1,2}';
            }
            description "Customer site prefix to be advertised into this VPN (e.g., 192.168.1.0/24)";
          }
        }
      }
    }
  }

  rpc validate-l3vpn-service {
    description "Validate an L3VPN service definition";
    input {
      leaf service-name {
        type string;
        mandatory true;
        description "Name of the service to validate";
      }
    }
    output {
      leaf validation-status {
        type enumeration {
          enum "valid" {
            value 0;
          }
          enum "invalid" {
            value 1;
          }
          enum "not-found" {
            value 2;
          }
        }
        description "Result of validation";
      }
      leaf-list errors {
        type string;
        description "List of validation errors, if any";
      }
    }
  }
}
